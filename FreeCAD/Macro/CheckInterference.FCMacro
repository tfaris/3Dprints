import itertools

import FreeCAD
import Draft, Part
from PySide import QtCore, QtGui


def errorDialog(msg):
    # Create a dialog Box
    # First argument is the icon used: QtGui.QMessageBox.{NoIcon, Information, Warning, Critical, Question} 
    diag = QtGui.QMessageBox(QtGui.QMessageBox.Information, 'COLLISION DETECTION Message:', msg)
    diag.setWindowModality(QtCore.Qt.ApplicationModal)
    diag.exec_()

selection = Gui.Selection.getSelectionEx()
original_bodies = list()

if len(selection) <= 1:
    for obj in Gui.ActiveDocument.Document.Objects:
        if (obj.isDerivedFrom('PartDesign::Body') or isinstance(obj, Part.Feature)) and obj.ViewObject.Visibility:
            original_bodies.append(obj)
else:
    for obj in selection:
        original_bodies.append(obj.Object)

if not original_bodies:
    errorDialog("Unable to select bodies automatically. Please select the bodies you want to check for interference.")
elif len(original_bodies) == 1:
    errorDialog("Select more than one body to check for interference.")
else:
    compare_groups = itertools.combinations(original_bodies, 2)
    # NOTE: Recompute must come before setting ShapeColor, for some reason.

    collision_detected = False
    intersection_bodies = list()
    for bodies in compare_groups:
        collision_obj = App.activeDocument().addObject("Part::MultiCommon","Intersection")
        collision_obj.Shapes = [Draft.clone(obj) for obj in bodies]
        App.ActiveDocument.recompute()
        collision_obj.ViewObject.ShapeColor = (1.0, 0.0, 0.0)
        intersection_bodies.append(collision_obj)

        if not collision_detected:
            collision_detected = collision_obj.Shape.Area > .00000001

    original_transparencies = [obj.ViewObject.Transparency for obj in original_bodies]
    showing_interference = True

    def toggle_collision_visibility(showing_interference):
        for i in range(0, len(original_bodies)):
            og_object = original_bodies[i]
            og_object.ViewObject.Transparency = 80 if showing_interference else original_transparencies[i]
        App.ActiveDocument.recompute()
        return showing_interference

    toggle_collision_visibility(showing_interference)

    class CheckInterferenceWidget(QtGui.QDockWidget):
        def init_ui(self):
            self.setWindowTitle("Check Interference")

            label1 = QtGui.QLabel(self)
            if collision_detected:
                label1.setText("COLLISION DETECTED")
                label1.setStyleSheet("QLabel { color: red; background-color: transparent; font-size: 20px; border: none; }")
            else:
                label1.setText("NO COLLISION DETECTED")
                label1.setStyleSheet("QLabel { color: rgb(95, 101, 4); background-color: transparent; font-size: 20px; border: none; }")
            self.set_position(label1, 10, 20)
            label1.resize(label1.sizeHint())

            interference_cbox = QtGui.QCheckBox("Show Interference", self)
            interference_cbox.setCheckState(QtCore.Qt.Checked)
            interference_cbox.stateChanged.connect(self.check_event)
            self.set_position(interference_cbox, label1.geometry().x(), label1.geometry().y() + 30)
            interference_cbox.resize(interference_cbox.sizeHint())

            label2 = QtGui.QLabel(self)
            label2.setText("Close this widget to reset view.")
            label2.setStyleSheet("QLabel { background-color: transparent; border: none; }")
            self.set_position(label2, interference_cbox.geometry().x(), interference_cbox.geometry().y() + 30)
            label2.resize(label2.sizeHint())

            # TODO: Add a list to the widget of the objects being compared

            self.resize(QtCore.QSize(300,300).expandedTo(self.minimumSizeHint()))

        def set_position(self, ctrl, x, y):
            geo = ctrl.geometry()
            geo.setX(x)
            geo.setY(y)
            ctrl.setGeometry(geo)

        def closeEvent(self, event):
            toggle_collision_visibility(False)
            for collision_obj in intersection_bodies:
                for shape in collision_obj.Shapes:
                    App.activeDocument().removeObject(shape.Name)
                App.activeDocument().removeObject(collision_obj.Name)

        def check_event(self, event):
            global showing_interference
            showing_interference = toggle_collision_visibility(not showing_interference)

    widget = CheckInterferenceWidget()
    widget.init_ui()
    FreeCADGui.getMainWindow().addDockWidget(
        QtCore.Qt.LeftDockWidgetArea,
        widget
    )
    widget.setFloating(True)
